module openconfig-platform-psu {

  yang-version "1";

  // namespace
  namespace "http://openconfig.net/yang/platform/psu";

  prefix "oc-platform-psu";

  // import some basic types
  import openconfig-extensions { prefix oc-ext; }
  import openconfig-types { prefix oc-types; }
  import openconfig-platform { prefix oc-platform; }


  // meta
  organization "OpenConfig working group";

  contact
    "OpenConfig working group
    www.openconfig.net";

  description
    "This module defines a schema for power supply components in
    the OpenConfig platform model.";

  oc-ext:openconfig-version "0.2.0";

   revision "2018-03-20" {
    description
      "Changed iput-current, input-voltage, output-power, 
      output-current, output-voltage to gauge parameters;
      Added slot-id.

      It is an informal version, which is only 
      available for alibaba internal discussion.
      If there is any question, please contact:
      Wang Lei, chiguang.wl@alibaba-inc.com;
      Chen Sai, chensai.cs@alibaba-inc.com.";
    reference "0.2.9";
  }
  revision "2018-01-16" {
    description
      "Changed admin state leaf name";
    reference "0.2.0";
  }

  revision "2017-12-21" {
    description
      "Initial revision";
    reference "0.1.0";
  }

  // identity statements

  // typedef statements

  // grouping statements

  grouping psu-config {
    description
      "Configuration data for power supply components";

    leaf enabled {
      type boolean;
      default true;
      description
        "Adminsitrative control on the on/off state of the power
        supply unit.";
    }
  }

  grouping psu-state {
    description
      "Operational state data for power supply components";

    leaf slot-id {
      type string;
      description
        "Identifier for the slot or chassis position in which the
        PSU is installed";
    }

    // TODO(aashaikh): May need to convert some of these to
    // interval statistics once decided on which leaves to include.
    leaf capacity {
      type oc-types:ieeefloat32;
      units watts;
      description
        "Maximum power capacity of the power supply.";
    }

    container iput-current {
      uses oc-types:avg-min-max-instant-stats-precision2-mA;
      description
        "The input current draw of the power supply.";
    }

    container iput-voltage {
      uses oc-types:avg-min-max-instant-stats-precision2-mV;
      description
        "Input voltage to the power supply.";
    }

    container output-current {
      uses oc-types:avg-min-max-instant-stats-precision2-mA;
      description
        "The output current supplied by the power supply.";
    }

    container output-voltage {
      uses oc-types:avg-min-max-instant-stats-precision2-mV;
      description
        "Output voltage supplied by the power supply.";
    }

    container output-power {
      uses oc-types:avg-min-max-instant-stats-precision2-watts;
      description
        "Output power supplied by the power supply.";
    }
  }

  // data definition statements

  // augment statements

  augment "/oc-platform:components/oc-platform:component/" +
    "oc-platform:power-supply/oc-platform:config" {
    description
      "Adds power supply data to component operational state.";

    uses psu-config;
  }

  augment "/oc-platform:components/oc-platform:component/" +
    "oc-platform:power-supply/oc-platform:state" {
    description
      "Adds power supply data to component operational state.";

    uses psu-config;
    uses psu-state;
  }


  // rpc statements

  // notification statements
}
