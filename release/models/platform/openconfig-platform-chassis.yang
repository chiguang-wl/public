module openconfig-platform-chassis {

  yang-version "1";

  // namespace
  namespace "http://openconfig.net/yang/platform/chassis";

  prefix "oc-chassis";

  import openconfig-extensions { prefix oc-ext; }
  import openconfig-platform-types {prefix oc-platform-types; }
  import openconfig-platform {prefix oc-platform;}


  // meta
  organization "OpenConfig working group";

  contact
    "OpenConfig working group
    www.openconfig.net";

  description
    "This module defines data related to CHASSIS components 
    in the openconfig-platform model.";

  oc-ext:openconfig-version "0.0.9";

  revision "2018-03-20" {
    description
      "Initial public release.
      It is an informal version, which is only 
      available for alibaba internal discussion.
      If there is any question, please contact:
      Wang Lei, chiguang.wl@alibaba-inc.com;
      Chen Sai, chensai.cs@alibaba-inc.com.";
    reference "0.0.9";
  }

  // grouping statements

  grouping slot-config {
    description
      "Configuration data for the slot of Chassis";

    leaf slot-id {
      type string;
      description
      "Identifier for the slot or chassis position in which the
      linecard is installed-- this will not be a
      configurable parameter on many implementations";
    }

    leaf description {
      type string;
      description
        "Description of the slot";
    }
  }

  grouping slot-state {
    description
      "Operational state data for chassis components";

    leaf-list possible-card-types {
      type oc-platform-types:card-type;
      description
        "Defined all the equipment types which can be installed 
        on the slot.";
    }
  }

  grouping slot-top {
    description
      "Top-level grouping for slot data";

    container slots {
      list slot {
        key "slot-id";

        leaf slot-id {
          type leafref {
            path "../config/slot-id";
          }
          description
            "References the slot id";
        }

        container config {
          description
            "Configuration data for chassis";

          uses slot-config;
        }

        container state {

          config false;

          description
            "Operational state data for chassis";

          uses slot-config;
          uses slot-state;
        }
      }
    }
  }


  grouping chassis-config {
    description
      "Configuration data for chassis components";
  }

  grouping chassis-state {
    description
      "Operational state data for chassis components";
  }

  // data definition statements

  // augment statements

  augment "/oc-platform:components/oc-platform:component/oc-platform:chassis" {
    description
      "Adding slot data to chassis";

    uses slot-top {
      when "current()/../oc-platform:state/" +
        "oc-platform:type = 'CHASSIS'" {
        description
          "Augment is active when component is of type CHASSIS";
      }
    }
  }
}
