module openconfig-platform-fan {

  yang-version "1";

  // namespace
  namespace "http://openconfig.net/yang/platform/fan";

  prefix "oc-fan";

  import openconfig-platform { prefix oc-platform; }
  import openconfig-extensions { prefix oc-ext; }
  import openconfig-platform-types {prefix oc-platform-types; }


  // meta
  organization "OpenConfig working group";

  contact
    "OpenConfig working group
    www.openconfig.net";

  description
    "This module defines data related to FAN components in the
    OpenConfig platform model.";

  oc-ext:openconfig-version "0.1.9";

  
  revision "2018-03-20" {
    description
      "Added slot-id to FAN state data; 
      change speed to a gauge parameter 
      with instant/min/max/avg stats.
      
      It is an informal version, which is only 
      available for alibaba internal discussion.
      If there is any question, please contact:
      Wang Lei, chiguang.wl@alibaba-inc.com;
      Chen Sai, chensai.cs@alibaba-inc.com.";
    reference "0.1.9";
  }
  revision "2018-01-18" {
    description
      "Initial revision";
    reference "0.1.0";
  }

  // identity statements

  // typedef statements

  // grouping statements

  grouping fan-state {
    description
      "Operational state data for fan components";

    leaf slot-id {
      type string;
      description
        "Identifier for the slot or chassis position in which the
        FAN is installed";
    }

    container speed {
      uses oc-platform-types:avg-min-max-instant-stats-rpm;
      description
        "fan speed rate. unit: rate per second";
    }
  }


  // data definition statements

  // augment statements

  augment "/oc-platform:components/oc-platform:component/" +
    "oc-platform:fan/oc-platform:state" {
    description
      "Adding fan data to component model";

    uses fan-state;
  }

}
